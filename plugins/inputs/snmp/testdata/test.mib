TEST DEFINITIONS ::= BEGIN

testOID ::= { 1 0 0 }

testTable OBJECT-TYPE
	SYNTAX SEQUENCE OF testTableEntry
	MAX-ACCESS not-accessible
	STATUS current
	::= { testOID 0 }

testTableEntry OBJECT-TYPE
	SYNTAX TestTableEntry
	MAX-ACCESS not-accessible
	STATUS current
	INDEX {
		server
	}
	::= { testTable 1 }

TestTableEntry ::=
	SEQUENCE {
		server OCTET STRING,
		connections  INTEGER,
		latency  OCTET STRING,
		description OCTET STRING,
	}

server OBJECT-TYPE
	SYNTAX OCTET STRING
	MAX-ACCESS read-only
	STATUS current
	::= { testTableEntry 1 }

connections OBJECT-TYPE
	SYNTAX INTEGER
	MAX-ACCESS read-only
	STATUS current
	::= { testTableEntry 2 }

latency OBJECT-TYPE
	SYNTAX OCTET STRING
	MAX-ACCESS read-only
	STATUS current
	::= { testTableEntry 3 }

description OBJECT-TYPE
	SYNTAX OCTET STRING
	MAX-ACCESS read-only
	STATUS current
	::= { testTableEntry 4 }

hostname OBJECT-TYPE
	SYNTAX OCTET STRING
	MAX-ACCESS read-only
	STATUS current
	::= { testOID 1 1 }

END
